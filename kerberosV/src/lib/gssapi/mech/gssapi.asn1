-- $Id: gssapi.asn1,v 1.1 2013/06/17 19:11:42 robert Exp $

GSS-API DEFINITIONS ::= BEGIN

IMPORTS heim_any_set FROM heim;

GSSAPIContextToken ::= [APPLICATION 0] IMPLICIT SEQUENCE {
	thisMech OBJECT IDENTIFIER,
	innerContextToken heim_any_set
}

END
